library package OOSEM {
    package 'OOSEM Measures' {
        abstract attribute <MOE> 'Measure of Effectivness';
        abstract attribute <MoP> 'Measure of Performance';
        view 'OOSEM Framework' : 'SysML Standard Diagrams'::gv;
    }
    package 'OOSEM View Prototypes' {
        view 'OOSEM View Prototypes' : 'SysML Standard Diagrams'::gv;
    }
    package 'OOSEM Package Template' {
        view 'OOSEM Package Template' : 'SysML Standard Diagrams'::gv;
    }
}
